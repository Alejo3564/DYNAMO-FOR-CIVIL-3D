(DEFUN C:CDNI ()(setvar "Cmdecho" 0)
(COMMAND"osmode""0")(COMMAND"ucs""w")(SETQ Qj" m.N")(SETQ Q@" m.E")(SETQ QQ(ENTSEL"\nSeleccione View: "))(SETQ Ql(GETREAL"\nEscala <ej. 1:50 = 50>:"))(INITGET"Si No")(SETQ Q&(GETKWORD"\nRotar texto Norte 180 Si/No <No>:"))(INITGET"Si No")(SETQ Q1(GETKWORD"\nRotar texto Este  180 Si/No <No>:"))(COMMAND"CMDECHO"0)(COMMAND"LAYER""M""C-ROAD-COOR IMPAR""C"9"""")(COMMAND"STYLE""COORDENADAS PP""ROMANS.SHX"""""20"""""")(SETQ Q#(* Ql 0.0016))(SETQ Q0(/ Ql 10.0))(SETQ Q$(* 2.0 Q#))(COMMAND"hatch""u"0 Q0"y"QQ"")(SETQ QO(ENTLAST))(COMMAND"explode"QO)(SETQ Q|(SSGET"P"))(COMMAND"change"Q|"""P""c""BYL""")(SETQ Q%(SSLENGTH Q|))(COMMAND"LAYER""M""C-ROAD-COOR TEXT IMPAR""C"251"""")(SETQ Q?j 0)(WHILE(< Q?j Q%)(SETQ Qjj(SSNAME Q| Q?j))(SETQ Q@j(ENTGET Qjj))(SETQ QQj(CDR(ASSOC 10 Q@j)))(SETQ Qlj(CDR(ASSOC 11 Q@j)))(SETQ Q&j(ANGLE Qlj QQj))(SETQ Q1j(DISTANCE QQj Qlj))(SETQ Q#j(NTH 0 QQj))(SETQ Q0j(NTH 1 QQj))(SETQ Q$j(NTH 0 Qlj))(SETQ QOj(NTH 1 Qlj))(IF(= 0.0(ANGLE QQj Qlj))(PROGN(SETQ Q|j(RTOS(NTH 1 QQj)2 0))(SETQ Q|j(STRCAT Q|j Qj))(SETQ Q%j(+ Q#j Q$))(SETQ Q?@(+ Q0j(* 0.30 Q#)))(SETQ Qj@(- Q$j(+ Q# Q$)))(SETQ Q@@(+ QOj(* 0.30 Q#)))(IF(="Si"Q&)(PROGN(SETQ QQ@(LIST Q%j(- Q?@(* 0.6 Q#))))(SETQ Ql@(LIST Qj@(- Q?@(* 0.6 Q#))))(SETQ Q&@ 180))(PROGN(SETQ QQ@(LIST Q%j Q?@))(SETQ Ql@(LIST Qj@ Q@@))(SETQ Q&@ 0))))(PROGN(SETQ Q|j(RTOS(NTH 0 QQj)2 0))(SETQ Q|j(STRCAT Q|j Q@))(SETQ Q%j(- Q#j(* 0.30 Q#)))(SETQ Q?@(+ Q0j Q$))(SETQ Qj@(- Q$j(* 0.30 Q#)))(SETQ Q@@(- QOj(+ Q# Q$)))(IF(="Si"Q1)(PROGN(SETQ QQ@(LIST(+ Q%j(* 0.6 Q#))(- Q?@ 0.0)))(SETQ Ql@(LIST(+ Qj@(* 0.6 Q#))(+ Q@@ 0.0)))(SETQ Q&@ 270))(PROGN(SETQ QQ@(LIST Q%j Q?@))(SETQ Ql@(LIST Qj@ Q@@))(SETQ Q&@ 90)))))(IF(>= Q1j(* 15.0 Q$))(PROGN(IF(OR(= 180 Q&@)(= 270 Q&@))(PROGN(COMMAND"layer""m"Q1@"")(COMMAND"text"Ql@ Q# Q&@ Q|j)(COMMAND"text""j""r"QQ@ Q# Q&@ Q|j))(PROGN(COMMAND"layer""m"Q1@"")(COMMAND"text"QQ@ Q# Q&@ Q|j)(COMMAND"text""j""r"Ql@ Q# Q&@ Q|j)))))(SETQ Q?j(+ 1 Q?j)))(COMMAND"ucs""p")(COMMAND"CMDECHO"1)(COMMAND"osmode""47"))(PRINC"\n              ESTE PROGRAMA DIBUJA LAS COORDENADAS EN UN PLANO
        \n   SELECCIONE LA VIEW, DIGITE LA ESCALA Y ESCOJA SI VA A ROTAR LOS TEXTOS.
        \n   Comando: CDNI
        \n                                          Ing. GERMAN VANEGAS VARGAS, 2000")(PRINC)
